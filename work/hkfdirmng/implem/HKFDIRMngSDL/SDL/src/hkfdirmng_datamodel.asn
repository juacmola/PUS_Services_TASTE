Hkfdirmng-Datamodel DEFINITIONS ::=
BEGIN
--  This file was generated automatically by OpenGEODE
IMPORTS
   RawTC, RxTC, FwdCommand, GPendingEvAction, GToReboot, GFwToHK-FDIR, GFwToBKG, Telecommand, Pr-time FROM SCTRE-DATAVIEW
   T-Int32, T-UInt32, T-Int8, T-UInt8, T-Boolean, T-Null-Record, T-Runtime-Error FROM TASTE-BasicTypes
   PID-Range, PID FROM System-Dataview;

Hkfdirmng-States ::= ENUMERATED {ready}

Hkfdirmng-Context ::= SEQUENCE {
   state Hkfdirmng-States,
   init-done BOOLEAN,
   sender PID,
   offspring PID,
   packet RawTC,
   time Pr-time
}

Hkfdirmng-T-Runtime-Error-Selection ::= ENUMERATED {noerror-present(1), encodeerror-present(2), decodeerror-present(3)}
END
